module GENERIC-RESOURCE-API-provider-impl {

    yang-version 1;
    namespace "org:onap:sdnc:northbound:GENERIC-RESOURCE-API:provider:impl";
    prefix "GENERIC-RESOURCE-API-provider-impl";

    import config { prefix config; revision-date 2013-04-05; }
    import opendaylight-md-sal-binding { prefix mdsal; revision-date 2013-10-28; }
    import opendaylight-sal-binding-broker-impl {
        prefix binding-impl;
        revision-date 2013-10-28;
    }

     description
        "This module contains the base YANG definitions for
        GENERIC-RESOURCE-API-provider impl implementation.";

    revision "2017-08-24" {
        description
            "ONAP Amsterdam version.";
    }

    // This is the definition of the service implementation as a module identity.
    identity GENERIC-RESOURCE-API-provider-impl {
            base config:module-type;

            // Specifies the prefix for generated java classes.
            config:java-name-prefix GENERIC-RESOURCE-APIProvider;
    }

    // Augments the 'configuration' choice node under modules/module.
    // We consume the three main services, RPCs, DataStore, and Notifications
    augment "/config:modules/config:module/config:configuration" {
        case GENERIC-RESOURCE-API-provider-impl {
            when "/config:modules/config:module/config:type = 'GENERIC-RESOURCE-API-provider-impl'";

            container rpc-registry {
                uses config:service-ref {
                    refine type {
                        mandatory true;
                        config:required-identity mdsal:binding-rpc-registry;
                    }
                }
            }

            container notification-publish-adapter {
                uses config:service-ref {
                    refine type {
                        mandatory true;
                        config:required-identity binding-impl:binding-new-notification-publish-service;
                    }
                }
            }

            container data-broker {
                uses config:service-ref {
                    refine type {
                        mandatory false;
                        config:required-identity mdsal:binding-async-data-broker;
                    }
                }
            }
        }
    }
}
